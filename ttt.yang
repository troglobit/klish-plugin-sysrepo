module ttt {
  namespace "urn:ttt";
  prefix ttt;

  import ietf-interfaces {
    prefix if;
  }


  leaf topleaf {
    type string;
  }

  leaf topleaf2 {
    type string;
  }

  leaf topempty {
    type empty;
  }

  container test {
    list iface {
      key "name";

      leaf name {
        type string;
      }

      leaf comment {
        type string;
      }

      leaf-list multi {
        type string;
      }

      leaf type {
        type enumeration {
          enum ethernet;
          enum ppp;
          enum dummy;
        }
      }

      leaf empty {
        type empty;
      }

    }
  }


  list acl {
    ordered-by user;
    key "name";

    leaf name {
      type string;
    }

    leaf iflink {
      type leafref {
        path "../../test/iface/name";
      }
    }

    leaf absiflink {
      type leafref {
        path "/if:interfaces/if:interface/if:name";
      }
    }

    leaf comment {
      type string;
    }

    leaf-list multi {
      ordered-by user;
      type leafref {
        path "../../test/iface/name";
      }
    }

  }


  list ref {
    ordered-by user;
    key "name";

    leaf name {
      type leafref {
        path "../../test/iface/name";
      }
    }

  }

  list rule {
    key "from to";

    leaf from {
      type string;
    }
    leaf to {
      type string;
    }

    leaf comment {
      type string;
    }

    leaf-list multi {
      ordered-by user;
      type string;
    }

  }


}
